;;; b1.lsp - generated from Template1.svg
;;; Creates native DraftSight LINE/TEXT entities. No SVG import dialog.

(defun _tpl-line (p1 p2 space)
  (entmakex
    (list
      (cons 0 "LINE")
      (cons 67 space)
      (cons 10 (list (car p1) (cadr p1) 0.0))
      (cons 11 (list (car p2) (cadr p2) 0.0))
    )
  )
)

(defun _tpl-text (pt h s space)
  (entmakex
    (list
      (cons 0 "TEXT")
      (cons 67 space)
      (cons 10 (list (car pt) (cadr pt) 0.0))
      (cons 40 h)
      (cons 1 s)
      (cons 50 0.0)
    )
  )
)

(defun c:LOADTEMPLATE (/ space)
  ;; 67=1 means Paper Space; 67=0 means Model Space.
  ;; In a layout, CVPORT=1 means you are actually in Paper Space.
  (setq space
    (if (= (getvar "TILEMODE") 1)
      0
      (if (= (getvar "CVPORT") 1) 1 0)
    )
  )
  (princ "\nDrawing Template1.svg as native geometry...")
  (_tpl-line (list 132.182528 0.005237) (list 132.182528 176.157129) space)
  (_tpl-line (list 0.005241 0.005237) (list 0.005241 176.157129) space)
  (_tpl-line (list 132.182528 176.157129) (list 0.005241 176.157129) space)
  (_tpl-line (list 0.005241 0.005237) (list 132.182528 0.005237) space)
  (_tpl-line (list 132.182528 20.852797) (list 77.068468 20.852797) space)
  (_tpl-line (list 122.612518 7.984067) (list 122.612518 4.214537) space)
  (_tpl-line (list 77.068468 20.852797) (list 77.068468 0.005237) space)
  (_tpl-line (list 97.749348 20.852797) (list 97.749348 0.005237) space)
  (_tpl-line (list 118.681788 4.214537) (list 118.681788 0.005237) space)
  (_tpl-line (list 77.068468 4.214537) (list 132.182528 4.214537) space)
  (_tpl-line (list 77.068468 7.984067) (list 132.182528 7.984067) space)
  (_tpl-line (list 123.189018 6.832267) (list 123.189018 7.565227) space)
  (_tpl-line (list 123.189018 7.565227) (list 123.492998 7.565227) space)
  (_tpl-line (list 123.492998 7.565227) (list 123.597818 7.523327) space)
  (_tpl-line (list 123.597818 7.523327) (list 123.629218 7.491927) space)
  (_tpl-line (list 123.629218 7.491927) (list 123.671118 7.429127) space)
  (_tpl-line (list 123.671118 7.429127) (list 123.671118 7.355827) space)
  (_tpl-line (list 123.671118 7.355827) (list 123.629218 7.282527) space)
  (_tpl-line (list 123.629218 7.282527) (list 123.597818 7.251127) space)
  (_tpl-line (list 123.597818 7.251127) (list 123.492998 7.219727) space)
  (_tpl-line (list 123.492998 7.219727) (list 123.189018 7.219727) space)
  (_tpl-line (list 123.430108 7.219687) (list 123.671188 6.832267) space)
  (_tpl-line (list 124.362998 6.832267) (list 123.912278 6.832267) space)
  (_tpl-line (list 123.912278 6.832267) (list 123.912278 7.565227) space)
  (_tpl-line (list 123.912278 7.565227) (list 124.362998 7.565227) space)
  (_tpl-line (list 123.912278 7.219687) (list 124.195288 7.219687) space)
  (_tpl-line (list 124.572638 7.565227) (list 124.855648 6.832267) space)
  (_tpl-line (list 124.855648 6.832267) (list 125.128178 7.565227) space)
  (_tpl-line (list 78.263418 3.293107) (list 78.221518 3.230307) space)
  (_tpl-line (list 78.221518 3.230307) (list 78.148118 3.157007) space)
  (_tpl-line (list 78.148118 3.157007) (list 78.085218 3.125607) space)
  (_tpl-line (list 78.085218 3.125607) (list 77.938468 3.125607) space)
  (_tpl-line (list 77.938468 3.125607) (list 77.875568 3.157007) space)
  (_tpl-line (list 77.875568 3.157007) (list 77.802168 3.230307) space)
  (_tpl-line (list 77.802168 3.230307) (list 77.770768 3.293107) space)
  (_tpl-line (list 77.770768 3.293107) (list 77.739268 3.408277) space)
  (_tpl-line (list 77.739268 3.408277) (list 77.739268 3.565347) space)
  (_tpl-line (list 77.739268 3.565347) (list 77.770768 3.680527) space)
  (_tpl-line (list 77.770768 3.680527) (list 77.802168 3.743327) space)
  (_tpl-line (list 77.802168 3.743327) (list 77.875568 3.816627) space)
  (_tpl-line (list 77.875568 3.816627) (list 77.938468 3.848027) space)
  (_tpl-line (list 77.938468 3.848027) (list 78.085218 3.848027) space)
  (_tpl-line (list 78.085218 3.848027) (list 78.148118 3.816627) space)
  (_tpl-line (list 78.148118 3.816627) (list 78.221518 3.743327) space)
  (_tpl-line (list 78.221518 3.743327) (list 78.263418 3.680527) space)
  (_tpl-line (list 78.462568 3.125567) (list 78.462568 3.848057) space)
  (_tpl-line (list 78.462568 3.502517) (list 78.944738 3.502517) space)
  (_tpl-line (list 78.944738 3.125567) (list 78.944738 3.848057) space)
  (_tpl-line (list 79.667998 3.125567) (list 79.227758 3.125567) space)
  (_tpl-line (list 79.227758 3.125567) (list 79.227758 3.848057) space)
  (_tpl-line (list 79.227758 3.848057) (list 79.667998 3.848057) space)
  (_tpl-line (list 79.227758 3.502517) (list 79.510768 3.502517) space)
  (_tpl-line (list 80.412218 3.293107) (list 80.370318 3.230307) space)
  (_tpl-line (list 80.370318 3.230307) (list 80.296918 3.157007) space)
  (_tpl-line (list 80.296918 3.157007) (list 80.234018 3.125607) space)
  (_tpl-line (list 80.234018 3.125607) (list 80.087268 3.125607) space)
  (_tpl-line (list 80.087268 3.125607) (list 80.024368 3.157007) space)
  (_tpl-line (list 80.024368 3.157007) (list 79.950968 3.230307) space)
  (_tpl-line (list 79.950968 3.230307) (list 79.919468 3.293107) space)
  (_tpl-line (list 79.919468 3.293107) (list 79.888068 3.408277) space)
  (_tpl-line (list 79.888068 3.408277) (list 79.888068 3.565347) space)
  (_tpl-line (list 79.888068 3.565347) (list 79.919468 3.680527) space)
  (_tpl-line (list 79.919468 3.680527) (list 79.950968 3.743327) space)
  (_tpl-line (list 79.950968 3.743327) (list 80.024368 3.816627) space)
  (_tpl-line (list 80.024368 3.816627) (list 80.087268 3.848027) space)
  (_tpl-line (list 80.087268 3.848027) (list 80.234008 3.848027) space)
  (_tpl-line (list 80.234008 3.848027) (list 80.296908 3.816627) space)
  (_tpl-line (list 80.296908 3.816627) (list 80.370308 3.743327) space)
  (_tpl-line (list 80.370308 3.743327) (list 80.412208 3.680527) space)
  (_tpl-line (list 80.611368 3.848057) (list 80.611368 3.125567) space)
  (_tpl-line (list 80.611368 3.366397) (list 81.093538 3.848057) space)
  (_tpl-line (list 80.789558 3.544407) (list 81.093538 3.125567) space)
  (_tpl-line (list 81.785348 3.125567) (list 81.334628 3.125567) space)
  (_tpl-line (list 81.334628 3.125567) (list 81.334628 3.848057) space)
  (_tpl-line (list 81.334628 3.848057) (list 81.785348 3.848057) space)
  (_tpl-line (list 81.334628 3.502517) (list 81.617638 3.502517) space)
  (_tpl-line (list 81.994988 3.125567) (list 82.236068 3.125567) space)
  (_tpl-line (list 82.236068 3.125567) (list 82.351368 3.156967) space)
  (_tpl-line (list 82.351368 3.156967) (list 82.414268 3.230267) space)
  (_tpl-line (list 82.414268 3.230267) (list 82.445668 3.293067) space)
  (_tpl-line (list 82.445668 3.293067) (list 82.487568 3.408237) space)
  (_tpl-line (list 82.487568 3.408237) (list 82.487568 3.565307) space)
  (_tpl-line (list 82.487568 3.565307) (list 82.445668 3.680487) space)
  (_tpl-line (list 82.445668 3.680487) (list 82.414268 3.743287) space)
  (_tpl-line (list 82.414268 3.743287) (list 82.351368 3.816587) space)
  (_tpl-line (list 82.351368 3.816587) (list 82.236068 3.847987) space)
  (_tpl-line (list 82.236068 3.847987) (list 81.994988 3.847987) space)
  (_tpl-line (list 81.994988 3.847987) (list 81.994988 3.125497) space)
  (_tpl-line (list 98.535488 19.753347) (list 98.535488 20.475847) space)
  (_tpl-line (list 98.294408 20.475847) (list 98.776578 20.475847) space)
  (_tpl-line (list 98.923318 19.753347) (list 98.923318 20.475847) space)
  (_tpl-line (list 99.436938 19.753347) (list 99.436938 20.475847) space)
  (_tpl-line (list 99.195848 20.475847) (list 99.678018 20.475847) space)
  (_tpl-line (list 99.824768 20.475847) (list 99.824768 19.753347) space)
  (_tpl-line (list 99.824768 19.753347) (list 100.233568 19.753347) space)
  (_tpl-line (list 100.851998 19.753347) (list 100.411758 19.753347) space)
  (_tpl-line (list 100.411758 19.753347) (list 100.411758 20.475847) space)
  (_tpl-line (list 100.411758 20.475847) (list 100.851998 20.475847) space)
  (_tpl-line (list 100.411758 20.130307) (list 100.694778 20.130307) space)
  (_tpl-line (list 119.237328 3.251217) (list 119.310728 3.188417) space)
  (_tpl-line (list 119.310728 3.188417) (list 119.415548 3.146517) space)
  (_tpl-line (list 119.415548 3.146517) (list 119.551818 3.146517) space)
  (_tpl-line (list 119.551818 3.146517) (list 119.656638 3.188417) space)
  (_tpl-line (list 119.656638 3.188417) (list 119.730038 3.251217) space)
  (_tpl-line (list 119.730038 3.251217) (list 119.730038 3.355927) space)
  (_tpl-line (list 119.730038 3.355927) (list 119.688138 3.429227) space)
  (_tpl-line (list 119.688138 3.429227) (list 119.656738 3.460627) space)
  (_tpl-line (list 119.656738 3.460627) (list 119.593838 3.492027) space)
  (_tpl-line (list 119.593838 3.492027) (list 119.373708 3.565327) space)
  (_tpl-line (list 119.373708 3.565327) (list 119.310808 3.596727) space)
  (_tpl-line (list 119.310808 3.596727) (list 119.279408 3.628127) space)
  (_tpl-line (list 119.279408 3.628127) (list 119.237508 3.701427) space)
  (_tpl-line (list 119.237508 3.701427) (list 119.237508 3.764227) space)
  (_tpl-line (list 119.237508 3.764227) (list 119.310908 3.837527) space)
  (_tpl-line (list 119.310908 3.837527) (list 119.415728 3.868927) space)
  (_tpl-line (list 119.415728 3.868927) (list 119.551998 3.868927) space)
  (_tpl-line (list 119.551998 3.868927) (list 119.656818 3.837527) space)
  (_tpl-line (list 119.656818 3.837527) (list 119.730218 3.764227) space)
  (_tpl-line (list 119.929138 3.146507) (list 119.929138 3.868997) space)
  (_tpl-line (list 119.929138 3.523467) (list 120.421788 3.523467) space)
  (_tpl-line (list 120.421788 3.146507) (list 120.421788 3.868997) space)
  (_tpl-line (list 121.145038 3.146507) (list 120.694318 3.146507) space)
  (_tpl-line (list 120.694318 3.146507) (list 120.694318 3.868997) space)
  (_tpl-line (list 120.694318 3.868997) (list 121.145038 3.868997) space)
  (_tpl-line (list 120.694318 3.523467) (list 120.977328 3.523467) space)
  (_tpl-line (list 121.805408 3.146507) (list 121.354678 3.146507) space)
  (_tpl-line (list 121.354678 3.146507) (list 121.354678 3.868997) space)
  (_tpl-line (list 121.354678 3.868997) (list 121.805408 3.868997) space)
  (_tpl-line (list 121.354678 3.523467) (list 121.637698 3.523467) space)
  (_tpl-line (list 122.256128 3.146507) (list 122.256128 3.868997) space)
  (_tpl-line (list 122.015038 3.868997) (list 122.497218 3.868997) space)
  (_tpl-line (list 98.336328 3.251217) (list 98.409728 3.188417) space)
  (_tpl-line (list 98.409728 3.188417) (list 98.514548 3.146517) space)
  (_tpl-line (list 98.514548 3.146517) (list 98.650818 3.146517) space)
  (_tpl-line (list 98.650818 3.146517) (list 98.755638 3.188417) space)
  (_tpl-line (list 98.755638 3.188417) (list 98.818538 3.251217) space)
  (_tpl-line (list 98.818538 3.251217) (list 98.818538 3.355927) space)
  (_tpl-line (list 98.818538 3.355927) (list 98.787138 3.429227) space)
  (_tpl-line (list 98.787138 3.429227) (list 98.755638 3.460627) space)
  (_tpl-line (list 98.755638 3.460627) (list 98.682238 3.492027) space)
  (_tpl-line (list 98.682238 3.492027) (list 98.472598 3.565327) space)
  (_tpl-line (list 98.472598 3.565327) (list 98.409698 3.596727) space)
  (_tpl-line (list 98.409698 3.596727) (list 98.378198 3.628127) space)
  (_tpl-line (list 98.378198 3.628127) (list 98.336298 3.701427) space)
  (_tpl-line (list 98.336298 3.701427) (list 98.336298 3.764227) space)
  (_tpl-line (list 98.336298 3.764227) (list 98.409698 3.837527) space)
  (_tpl-line (list 98.409698 3.837527) (list 98.514518 3.868927) space)
  (_tpl-line (list 98.514518 3.868927) (list 98.650778 3.868927) space)
  (_tpl-line (list 98.650778 3.868927) (list 98.755598 3.837527) space)
  (_tpl-line (list 98.755598 3.837527) (list 98.818498 3.764227) space)
  (_tpl-line (list 99.552238 3.324517) (list 99.510338 3.251217) space)
  (_tpl-line (list 99.510338 3.251217) (list 99.447438 3.188417) space)
  (_tpl-line (list 99.447438 3.188417) (list 99.374038 3.146517) space)
  (_tpl-line (list 99.374038 3.146517) (list 99.237768 3.146517) space)
  (_tpl-line (list 99.237768 3.146517) (list 99.164368 3.188417) space)
  (_tpl-line (list 99.164368 3.188417) (list 99.101468 3.251217) space)
  (_tpl-line (list 99.101468 3.251217) (list 99.070068 3.324517) space)
  (_tpl-line (list 99.070068 3.324517) (list 99.028168 3.429227) space)
  (_tpl-line (list 99.028168 3.429227) (list 99.028168 3.596757) space)
  (_tpl-line (list 99.028168 3.596757) (list 99.070068 3.701467) space)
  (_tpl-line (list 99.070068 3.701467) (list 99.101468 3.764267) space)
  (_tpl-line (list 99.101468 3.764267) (list 99.164368 3.837567) space)
  (_tpl-line (list 99.164368 3.837567) (list 99.237768 3.868967) space)
  (_tpl-line (list 99.237768 3.868967) (list 99.374038 3.868967) space)
  (_tpl-line (list 99.374038 3.868967) (list 99.447438 3.837567) space)
  (_tpl-line (list 99.447438 3.837567) (list 99.510338 3.764267) space)
  (_tpl-line (list 99.510338 3.764267) (list 99.552238 3.701467) space)
  (_tpl-line (list 99.761878 3.146507) (list 100.034408 3.868997) space)
  (_tpl-line (list 100.034408 3.868997) (list 100.306938 3.146507) space)
  (_tpl-line (list 99.866698 3.387337) (list 100.202118 3.387337) space)
  (_tpl-line (list 100.516578 3.868997) (list 100.516578 3.146507) space)
  (_tpl-line (list 100.516578 3.146507) (list 100.935858 3.146507) space)
  (_tpl-line (list 101.554298 3.146507) (list 101.114048 3.146507) space)
  (_tpl-line (list 101.114048 3.146507) (list 101.114048 3.868997) space)
  (_tpl-line (list 101.114048 3.868997) (list 101.554298 3.868997) space)
  (_tpl-line (list 101.114048 3.523467) (list 101.386578 3.523467) space)
  (_tpl-line (list 77.718348 6.779917) (list 77.969918 6.779917) space)
  (_tpl-line (list 77.969918 6.779917) (list 78.074738 6.821817) space)
  (_tpl-line (list 78.074738 6.821817) (list 78.137638 6.884617) space)
  (_tpl-line (list 78.137638 6.884617) (list 78.169038 6.957917) space)
  (_tpl-line (list 78.169038 6.957917) (list 78.210938 7.062627) space)
  (_tpl-line (list 78.210938 7.062627) (list 78.210938 7.230157) space)
  (_tpl-line (list 78.210938 7.230157) (list 78.169038 7.334867) space)
  (_tpl-line (list 78.169038 7.334867) (list 78.137638 7.397667) space)
  (_tpl-line (list 78.137638 7.397667) (list 78.074738 7.470967) space)
  (_tpl-line (list 78.074738 7.470967) (list 77.969918 7.502367) space)
  (_tpl-line (list 77.969918 7.502367) (list 77.718348 7.502367) space)
  (_tpl-line (list 77.718348 7.502367) (list 77.718348 6.779877) space)
  (_tpl-line (list 78.452088 6.779917) (list 78.452088 7.502407) space)
  (_tpl-line (list 78.452088 7.502407) (list 78.766548 7.502407) space)
  (_tpl-line (list 78.766548 7.502407) (list 78.871368 7.471007) space)
  (_tpl-line (list 78.871368 7.471007) (list 78.902768 7.439607) space)
  (_tpl-line (list 78.902768 7.439607) (list 78.934268 7.366307) space)
  (_tpl-line (list 78.934268 7.366307) (list 78.934268 7.303507) space)
  (_tpl-line (list 78.934268 7.303507) (list 78.902768 7.230207) space)
  (_tpl-line (list 78.902768 7.230207) (list 78.871368 7.198807) space)
  (_tpl-line (list 78.871368 7.198807) (list 78.766548 7.156907) space)
  (_tpl-line (list 78.766548 7.156907) (list 78.452088 7.156907) space)
  (_tpl-line (list 78.693178 7.156867) (list 78.934258 6.779917) space)
  (_tpl-line (list 79.175348 6.779917) (list 79.458358 7.502407) space)
  (_tpl-line (list 79.458358 7.502407) (list 79.730888 6.779917) space)
  (_tpl-line (list 79.280168 7.020737) (list 79.626068 7.020737) space)
  (_tpl-line (list 79.940528 7.502407) (list 80.118718 6.779917) space)
  (_tpl-line (list 80.118718 6.779917) (list 80.286428 7.502407) space)
  (_tpl-line (list 80.286428 7.502407) (list 80.464618 6.779917) space)
  (_tpl-line (list 80.464618 6.779917) (list 80.632338 7.502407) space)
  (_tpl-line (list 80.768598 6.779917) (list 80.768598 7.502407) space)
  (_tpl-line (list 80.768598 7.502407) (list 81.261248 6.779917) space)
  (_tpl-line (list 81.261248 6.779917) (list 81.261248 7.502407) space)
  (_tpl-line (list 82.194138 6.779917) (list 82.508598 6.779917) space)
  (_tpl-line (list 82.508598 6.779917) (list 82.613418 6.821817) space)
  (_tpl-line (list 82.613418 6.821817) (list 82.644818 6.853217) space)
  (_tpl-line (list 82.644818 6.853217) (list 82.676318 6.916017) space)
  (_tpl-line (list 82.676318 6.916017) (list 82.676318 7.020717) space)
  (_tpl-line (list 82.676318 7.020717) (list 82.644818 7.094017) space)
  (_tpl-line (list 82.644818 7.094017) (list 82.613418 7.125417) space)
  (_tpl-line (list 82.613418 7.125417) (list 82.508598 7.156817) space)
  (_tpl-line (list 82.508598 7.156817) (list 82.613418 7.198717) space)
  (_tpl-line (list 82.613418 7.198717) (list 82.644818 7.230117) space)
  (_tpl-line (list 82.644818 7.230117) (list 82.676318 7.303417) space)
  (_tpl-line (list 82.676318 7.303417) (list 82.676318 7.366217) space)
  (_tpl-line (list 82.676318 7.366217) (list 82.644818 7.439517) space)
  (_tpl-line (list 82.644818 7.439517) (list 82.613418 7.470917) space)
  (_tpl-line (list 82.613418 7.470917) (list 82.508598 7.502317) space)
  (_tpl-line (list 82.508598 7.502317) (list 82.194138 7.502317) space)
  (_tpl-line (list 82.194138 7.502317) (list 82.194138 6.779827) space)
  (_tpl-line (list 82.194138 7.156867) (list 82.508598 7.156867) space)
  (_tpl-line (list 82.917398 7.502407) (list 83.200408 7.156867) space)
  (_tpl-line (list 83.200408 7.156867) (list 83.200408 6.779917) space)
  (_tpl-line (list 83.200408 7.156867) (list 83.472938 7.502407) space)
  (_tpl-line (list 106.543698 0.937147) (list 106.543698 2.151777) space)
  (_tpl-line (list 106.543698 2.151777) (list 107.350808 0.937147) space)
  (_tpl-line (list 107.350808 0.937147) (list 107.350808 2.151777) space)
  (_tpl-line (list 108.220808 0.937147) (list 108.220808 2.151777) space)
  (_tpl-line (list 107.822498 2.151777) (list 108.629608 2.151777) space)
  (_tpl-line (list 108.860208 1.115157) (list 108.975508 0.999977) space)
  (_tpl-line (list 108.975508 0.999977) (list 109.153698 0.937177) space)
  (_tpl-line (list 109.153698 0.937177) (list 109.384308 0.937177) space)
  (_tpl-line (list 109.384308 0.937177) (list 109.562498 0.999977) space)
  (_tpl-line (list 109.562498 0.999977) (list 109.677798 1.115157) space)
  (_tpl-line (list 109.677798 1.115157) (list 109.677798 1.282687) space)
  (_tpl-line (list 109.677798 1.282687) (list 109.614898 1.408337) space)
  (_tpl-line (list 109.614898 1.408337) (list 109.562498 1.460737) space)
  (_tpl-line (list 109.562498 1.460737) (list 109.447198 1.523537) space)
  (_tpl-line (list 109.447198 1.523537) (list 109.090808 1.638717) space)
  (_tpl-line (list 109.090808 1.638717) (list 108.975508 1.680617) space)
  (_tpl-line (list 108.975508 1.680617) (list 108.933608 1.743417) space)
  (_tpl-line (list 108.933608 1.743417) (list 108.860208 1.858597) space)
  (_tpl-line (list 108.860208 1.858597) (list 108.860208 1.973777) space)
  (_tpl-line (list 108.860208 1.973777) (list 108.975508 2.088957) space)
  (_tpl-line (list 108.975508 2.088957) (list 109.153698 2.151757) space)
  (_tpl-line (list 109.153698 2.151757) (list 109.384308 2.151757) space)
  (_tpl-line (list 109.384308 2.151757) (list 109.562498 2.088957) space)
  (_tpl-line (list 109.562498 2.088957) (list 109.677798 1.973777) space)
  (_tpl-line (list 77.246668 14.559787) (list 132.318788 14.580687) space)
  (_tpl-line (list 98.462118 13.439397) (list 98.462118 14.161897) space)
  (_tpl-line (list 98.462118 14.161897) (list 98.745128 13.439397) space)
  (_tpl-line (list 98.745128 13.439397) (list 99.017658 14.161897) space)
  (_tpl-line (list 99.017658 14.161897) (list 99.017658 13.439397) space)
  (_tpl-line (list 99.499828 13.439397) (list 99.636088 13.439397) space)
  (_tpl-line (list 99.636088 13.439397) (list 99.709488 13.470797) space)
  (_tpl-line (list 99.709488 13.470797) (list 99.772388 13.544097) space)
  (_tpl-line (list 99.772388 13.544097) (list 99.814288 13.606897) space)
  (_tpl-line (list 99.814288 13.606897) (list 99.845688 13.711607) space)
  (_tpl-line (list 99.845688 13.711607) (list 99.845688 13.879137) space)
  (_tpl-line (list 99.845688 13.879137) (list 99.814288 13.983847) space)
  (_tpl-line (list 99.814288 13.983847) (list 99.772388 14.057147) space)
  (_tpl-line (list 99.772388 14.057147) (list 99.709488 14.119947) space)
  (_tpl-line (list 99.709488 14.119947) (list 99.636088 14.161847) space)
  (_tpl-line (list 99.636088 14.161847) (list 99.499828 14.161847) space)
  (_tpl-line (list 99.499828 14.161847) (list 99.426428 14.119947) space)
  (_tpl-line (list 99.426428 14.119947) (list 99.363528 14.057147) space)
  (_tpl-line (list 99.363528 14.057147) (list 99.332028 13.983847) space)
  (_tpl-line (list 99.332028 13.983847) (list 99.290128 13.879137) space)
  (_tpl-line (list 99.290128 13.879137) (list 99.290128 13.711607) space)
  (_tpl-line (list 99.290128 13.711607) (list 99.332028 13.606897) space)
  (_tpl-line (list 99.332028 13.606897) (list 99.363528 13.544097) space)
  (_tpl-line (list 99.363528 13.544097) (list 99.426428 13.470797) space)
  (_tpl-line (list 99.426428 13.470797) (list 99.499828 13.439397) space)
  (_tpl-line (list 100.055378 13.439397) (list 100.296458 13.439397) space)
  (_tpl-line (list 100.296458 13.439397) (list 100.401278 13.470797) space)
  (_tpl-line (list 100.401278 13.470797) (list 100.474678 13.544097) space)
  (_tpl-line (list 100.474678 13.544097) (list 100.506078 13.606897) space)
  (_tpl-line (list 100.506078 13.606897) (list 100.537478 13.711607) space)
  (_tpl-line (list 100.537478 13.711607) (list 100.537478 13.879137) space)
  (_tpl-line (list 100.537478 13.879137) (list 100.506078 13.983847) space)
  (_tpl-line (list 100.506078 13.983847) (list 100.474678 14.057147) space)
  (_tpl-line (list 100.474678 14.057147) (list 100.401278 14.119947) space)
  (_tpl-line (list 100.401278 14.119947) (list 100.296458 14.161847) space)
  (_tpl-line (list 100.296458 14.161847) (list 100.055378 14.161847) space)
  (_tpl-line (list 100.055378 14.161847) (list 100.055378 13.439347) space)
  (_tpl-line (list 101.229358 13.439397) (list 100.778628 13.439397) space)
  (_tpl-line (list 100.778628 13.439397) (list 100.778628 14.161897) space)
  (_tpl-line (list 100.778628 14.161897) (list 101.229358 14.161897) space)
  (_tpl-line (list 100.778628 13.816357) (list 101.061638 13.816357) space)
  (_tpl-line (list 101.438988 14.161897) (list 101.438988 13.439397) space)
  (_tpl-line (list 101.438988 13.439397) (list 101.858268 13.439397) space)
  (_tpl-line (list 98.451638 6.853207) (list 98.692718 6.853207) space)
  (_tpl-line (list 98.692718 6.853207) (list 98.797538 6.895107) space)
  (_tpl-line (list 98.797538 6.895107) (list 98.870938 6.968407) space)
  (_tpl-line (list 98.870938 6.968407) (list 98.902338 7.031207) space)
  (_tpl-line (list 98.902338 7.031207) (list 98.933838 7.135917) space)
  (_tpl-line (list 98.933838 7.135917) (list 98.933838 7.303447) space)
  (_tpl-line (list 98.933838 7.303447) (list 98.902338 7.408157) space)
  (_tpl-line (list 98.902338 7.408157) (list 98.870938 7.481457) space)
  (_tpl-line (list 98.870938 7.481457) (list 98.797538 7.544257) space)
  (_tpl-line (list 98.797538 7.544257) (list 98.692718 7.586157) space)
  (_tpl-line (list 98.692718 7.586157) (list 98.451638 7.586157) space)
  (_tpl-line (list 98.451638 7.586157) (list 98.451638 6.853197) space)
  (_tpl-line (list 99.185368 7.586167) (list 99.353078 6.853207) space)
  (_tpl-line (list 99.353078 6.853207) (list 99.531278 7.586167) space)
  (_tpl-line (list 99.531278 7.586167) (list 99.709468 6.853207) space)
  (_tpl-line (list 99.709468 6.853207) (list 99.866698 7.586167) space)
  (_tpl-line (list 100.359348 7.135927) (list 100.537548 7.135927) space)
  (_tpl-line (list 100.537548 7.135927) (list 100.537548 7.031217) space)
  (_tpl-line (list 100.537548 7.031217) (list 100.495648 6.968417) space)
  (_tpl-line (list 100.495648 6.968417) (list 100.432748 6.895117) space)
  (_tpl-line (list 100.432748 6.895117) (list 100.359348 6.853217) space)
  (_tpl-line (list 100.359348 6.853217) (list 100.212608 6.853217) space)
  (_tpl-line (list 100.212608 6.853217) (list 100.149708 6.895117) space)
  (_tpl-line (list 100.149708 6.895117) (list 100.076308 6.968417) space)
  (_tpl-line (list 100.076308 6.968417) (list 100.055308 7.031217) space)
  (_tpl-line (list 100.055308 7.031217) (list 100.013408 7.135927) space)
  (_tpl-line (list 100.013408 7.135927) (list 100.013408 7.303457) space)
  (_tpl-line (list 100.013408 7.303457) (list 100.055308 7.408167) space)
  (_tpl-line (list 100.055308 7.408167) (list 100.076308 7.481467) space)
  (_tpl-line (list 100.076308 7.481467) (list 100.149708 7.544267) space)
  (_tpl-line (list 100.149708 7.544267) (list 100.212608 7.586167) space)
  (_tpl-line (list 100.212608 7.586167) (list 100.359348 7.586167) space)
  (_tpl-line (list 100.359348 7.586167) (list 100.432748 7.544267) space)
  (_tpl-line (list 100.432748 7.544267) (list 100.495648 7.481467) space)
  (_tpl-line (list 100.495648 7.481467) (list 100.537548 7.408167) space)
  (_tpl-line (list 101.397058 6.853207) (list 101.397058 7.586167) space)
  (_tpl-line (list 101.397058 7.586167) (list 101.879238 6.853207) space)
  (_tpl-line (list 101.879238 6.853207) (list 101.879238 7.586167) space)
  (_tpl-line (list 102.162248 7.586167) (list 102.162248 7.062627) space)
  (_tpl-line (list 102.162248 7.062627) (list 102.204148 6.968427) space)
  (_tpl-line (list 102.204148 6.968427) (list 102.267048 6.895127) space)
  (_tpl-line (list 102.267048 6.895127) (list 102.361348 6.853227) space)
  (_tpl-line (list 102.361348 6.853227) (list 102.445248 6.853227) space)
  (_tpl-line (list 102.445248 6.853227) (list 102.539548 6.895127) space)
  (_tpl-line (list 102.539548 6.895127) (list 102.612948 6.968427) space)
  (_tpl-line (list 102.612948 6.968427) (list 102.644348 7.062627) space)
  (_tpl-line (list 102.644348 7.062627) (list 102.644348 7.586167) space)
  (_tpl-line (list 102.927428 6.853207) (list 102.927428 7.586167) space)
  (_tpl-line (list 102.927428 7.586167) (list 103.199958 6.853207) space)
  (_tpl-line (list 103.199958 6.853207) (list 103.472488 7.586167) space)
  (_tpl-line (list 103.472488 7.586167) (list 103.472488 6.853207) space)
  (_tpl-line (list 103.755498 6.853207) (list 104.069958 6.853207) space)
  (_tpl-line (list 104.069958 6.853207) (list 104.174778 6.895107) space)
  (_tpl-line (list 104.174778 6.895107) (list 104.206278 6.926507) space)
  (_tpl-line (list 104.206278 6.926507) (list 104.237678 6.989307) space)
  (_tpl-line (list 104.237678 6.989307) (list 104.237678 7.104487) space)
  (_tpl-line (list 104.237678 7.104487) (list 104.206278 7.167287) space)
  (_tpl-line (list 104.206278 7.167287) (list 104.174778 7.209187) space)
  (_tpl-line (list 104.174778 7.209187) (list 104.069958 7.240587) space)
  (_tpl-line (list 104.069958 7.240587) (list 104.174778 7.271987) space)
  (_tpl-line (list 104.174778 7.271987) (list 104.206278 7.303387) space)
  (_tpl-line (list 104.206278 7.303387) (list 104.237678 7.376687) space)
  (_tpl-line (list 104.237678 7.376687) (list 104.237678 7.449987) space)
  (_tpl-line (list 104.237678 7.449987) (list 104.206278 7.512787) space)
  (_tpl-line (list 104.206278 7.512787) (list 104.174778 7.544187) space)
  (_tpl-line (list 104.174778 7.544187) (list 104.069958 7.586087) space)
  (_tpl-line (list 104.069958 7.586087) (list 103.755498 7.586087) space)
  (_tpl-line (list 103.755498 7.586087) (list 103.755498 6.853127) space)
  (_tpl-line (list 103.755498 7.240627) (list 104.069958 7.240627) space)
  (_tpl-line (list 104.929478 6.853207) (list 104.478758 6.853207) space)
  (_tpl-line (list 104.478758 6.853207) (list 104.478758 7.586167) space)
  (_tpl-line (list 104.478758 7.586167) (list 104.929478 7.586167) space)
  (_tpl-line (list 104.478758 7.240627) (list 104.761768 7.240627) space)
  (_tpl-line (list 105.139118 6.853207) (list 105.139118 7.586167) space)
  (_tpl-line (list 105.139118 7.586167) (list 105.453578 7.586167) space)
  (_tpl-line (list 105.453578 7.586167) (list 105.558398 7.544267) space)
  (_tpl-line (list 105.558398 7.544267) (list 105.589798 7.512867) space)
  (_tpl-line (list 105.589798 7.512867) (list 105.631698 7.450067) space)
  (_tpl-line (list 105.631698 7.450067) (list 105.631698 7.376767) space)
  (_tpl-line (list 105.631698 7.376767) (list 105.589798 7.303467) space)
  (_tpl-line (list 105.589798 7.303467) (list 105.558398 7.272067) space)
  (_tpl-line (list 105.558398 7.272067) (list 105.453578 7.240667) space)
  (_tpl-line (list 105.453578 7.240667) (list 105.139118 7.240667) space)
  (_tpl-line (list 105.380198 7.240627) (list 105.631768 6.853207) space)
  (_tpl-line (list 63.075081 160.220424) (list 63.075081 162.869561) space)
  (_tpl-line (list 62.194598 162.869561) (list 63.955565 162.869561) space)
  (_tpl-line (list 64.458698 160.220424) (list 64.458698 162.869561) space)
  (_tpl-line (list 66.355928 160.220424) (list 66.355928 162.869561) space)
  (_tpl-line (list 65.475448 162.869561) (list 67.236418 162.869561) space)
  (_tpl-line (list 67.739548 162.869561) (list 67.739548 160.220424) space)
  (_tpl-line (list 67.739548 160.220424) (list 69.259428 160.220424) space)
  (_tpl-line (list 71.513048 160.220424) (list 69.888348 160.220424) space)
  (_tpl-line (list 69.888348 160.220424) (list 69.888348 162.869561) space)
  (_tpl-line (list 69.888348 162.869561) (list 71.513048 162.869561) space)
  (_tpl-line (list 69.888348 161.602582) (list 70.905088 161.602582) space)
  (_tpl-line (list 62.194598 159.696879) (list 72.288708 159.696879) space)
  (_tpl-text (list 77.277138 19.778807) 1.000000 "Production START DATE" space)
  (_tpl-text (list 77.250372 13.317771) 1.000001 "PRODUCTION END DATE" space)
  (princ "\nTemplate complete.")
  (princ)
)

;;; Auto-run when loaded:
(c:LOADTEMPLATE)
